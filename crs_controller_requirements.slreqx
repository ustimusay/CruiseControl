# crs_controller_requirements

## IC: Input_Conditioning: 入力前処理 (Functional)
crs_controllerのInput_Conditioningサブシステムに関する機能要求。生センサ・ボタン信号を後段が使用するブール信号に変換する。

### IC-001: ボタン立ち上がりエッジ検出 (Functional)
enbl, cncl, set, resume, inc, dec の各ボタン入力について立ち上がりエッジを検出し、対応する _rise 出力に 1サンプル幅の true パルスを出力すること。

### IC-002: ボタン長押し検出 (Functional)
inc または dec ボタンが 500 ms (Ts=0.01 s × 50 サンプル) 以上継続して押された場合、inc_held / dec_held をそれぞれ true に保持すること。

### IC-003: ブレーキ圧しきい値判定 (Functional)
brakeP が Brake_Threshold (5 kPa) を超えた場合に brake_active = true を出力すること。

### IC-004: キー位置デコード (Functional)
key 入力が 2 (イグニッション ON 位置) のとき key_on = true を出力すること。

### IC-005: ギア位置デコード (Functional)
gear 入力が 2 (ドライブ位置) のとき gear_drive = true を出力すること。

### IC-006: 速度範囲判定 (Functional)
Spd_Min (40 km/h) <= vehicle_speed <= Spd_Max (100 km/h) のとき speed_in_range = true を出力すること。

## MM: Mode_Manager: 動作モード管理 (Container)

### MM-001: CC 動作モード遷移制御 (Functional)
モード管理は Disabled / Enabled / Activated の3状態を持ち、enbl・key_on・gear_drive・speed_in_range・brake_active・cancel の各信号に基づいて遷移すること。遷移優先度: 最高は key 非ON またはenblトグルによる Disabled 遷移。

### MM-002: アクセル操作オーバーライド検出 (Functional)
While Activated 状態中, driver_throttle が Drv_Override_Hi (15) を超えた場合、accel_override を true とし PID 制御を一時停止すること。driver_throttle が Drv_Override_Lo を下回るまで override 状態を保持すること。

## TSM: Target_Speed_Manager: 目標速度管理 (Container)

### TSM-001: 目標速度の初期設定 (Functional)
When set_rise が検出されたとき、cc_target_speed を現在の vehicle_speed にクランプした値に設定すること。

### TSM-002: 前回目標速度の復元 (Functional)
When resume_rise が検出され has_prev_target が true のとき、cc_target_speed を前回設定値 prev_target に復元すること。

### TSM-003: 目標速度インクリメント (Functional)
When inc_rise (短押し) が検出されたとき cc_target_speed に Spd_Inc_Coarse (1 km/h) を加算すること。While inc_held (長押し) 中は Spd_Inc_Fine (5 km/h/s) を加算し続けること。上限は Spd_Max (100 km/h)。

### TSM-004: 目標速度デクリメント (Functional)
When dec_rise (短押し) が検出されたとき cc_target_speed から Spd_Inc_Coarse (1 km/h) を減算すること。While dec_held (長押し) 中は Spd_Inc_Fine (5 km/h/s) を減算し続けること。下限は Spd_Min (40 km/h)。

### TSM-005: アクセル操作解除後の速度更新 (Functional)
When accel_override が true から false に変化したとき、cc_target_speed を現在の vehicle_speed に更新すること。

### TSM-006: 目標速度出力範囲クランプ (Functional)
cc_target_speed の出力値は常に [Spd_Min (40 km/h), Spd_Max (100 km/h)] の範囲内に制限すること。

## PID: PID_Throttle_Controller: PID スロットル制御 (Container)

### PID-001: 速度誤差演算 (Functional)
The controller shall compute speed error e(k) = cc_target_speed - vehicle_speed at each sample step (Ts = 0.01 s).

### PID-002: PID 演算・積分器制御 (Functional)
The controller shall compute throttle command u(k) = Kp (20)*e + Ki (0.2)*integral(e) + Kd (-0.0249)*de/dt。Anti-windup はクランプ方式とし、出力飽和中かつ誤差が飽和方向の場合に積分を停止すること。Enabled→Activated 移行時は積分初期値を driver_throttle に設定すること (バンプレス遷移)。Disabled 移行時は積分器をリセットすること。

### PID-003: PID 出力ゲート (Functional)
When enable_pid が false のとき、PID 出力をゼロにマスクして pid_throttle = 0 を出力すること。

## OL: Output_Logic: 出力選択 (Container)

### OL-001: CC アクティベーション判定 (Functional)
op_mode が Activated (2) かつ accel_override が false のとき、use_pid フラグを true とすること。

### OL-002: スロットル出力選択と飽和制限 (Functional)
When use_pid が true のとき cc_throttle = clamp(pid_throttle, throttle_min (0), throttle_max (100)) を出力すること。If use_pid が false のとき cc_throttle = driver_throttle を出力すること。
